# eVTOL_Requirements

## #1: Motor power 200kW+ (Functional)
Each motor should be rated above 150kW

## #2: Passive cell balancing (Functional)
All 100 cells should be capable of balancing cells passively

## #3: Battery Pack should be of minimum 400V (Functional)
400V+ battery pack

## #4: Battery voltage drop (Functional)
Battery voltage drop should not be more than 80% of battery Voltage.

## #6: Fault Management (Functional)
Faults:
Over Current
High Temperature
Low Temperature
Over Voltage
Under Voltage

## #7: Calculate SOC using EKF/UKF (Functional)
Use Kalman filter to estimate SOC

## #8: Flight controller (Functional)
Flight controller should activate motor control algorithm
