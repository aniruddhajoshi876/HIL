# Requirements

## #1: Min and Max controlled Voltage per cell (2.4V to 4.2V) (Functional)
Controller requirement: Min and Max controlled Voltage per cell in the battery pack to remain between 2.4V and 4.2V

## #2: Fault management system (Functional)
Controller requirement: Implement a fault management system
Manage faults in the system:
1) Over Voltage
2) Under Voltage
3) Over Current
4) High temperature
5) Low temperature

### #11: Voltage fault management (Functional)
Manage over-voltage and under-voltage faults for each cell

### #14: Over-current fault management (Functional)
Over Current should be managed for each cell

### #15: High and low temperature management (Functional)
High and low temperature faults should be managed for each cell

## #4: Controller's update frequnecy (Functional)
Controller requirement: Controller's sample rate should be 1kHz

## #7: SOC estimation using EKF/UKF (Functional)
Controller requirement: Use Kalman filter to estimate SOC of the battery pack

## #8: Override Voltage and Temperature (Functional)
Testing requirement: Function to override Voltage and temperature values during run-time for testing extreme conditions

## #17: Passive Balancing of cells (Functional)
Controller requirement: Implement passive balacing for cells in the battery pack
